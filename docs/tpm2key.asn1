TPM-Key-Module

 DEFINITIONS IMPLICIT TAGS ::=
 BEGIN

 --
 -- Should import this but TCG hasn't yet published it or .10
 --
 id-tpmkey OBJECT IDENTIFIER ::=
   {joint-iso-itu-t(2) international-organizations(23) 133 10 1}

 --
 -- OIDs defined by this RFC
 --
 id-loadablekey OBJECT IDENTIFIER ::=  {id-tpmkey 3}
 id-importablekey OBJECT IDENTIFIER ::=  {id-tpmkey 4}
 id-sealedkey OBJECT IDENTIFIER ::= {id-tpmkey 5}

 TPMPolicy ::= SEQUENCE {
   commandCode   [0] EXPLICIT INTEGER,
   commandPolicy [1] EXPLICIT OCTET STRING
 }

 TPMAuthPolicy ::= SEQUENCE {
   name    [0] EXPLICIT UTF8String OPTIONAL,
   policy  [1] EXPLICIT SEQUENCE OF TPMPolicy
 }

 TPMKeyType ::= OBJECT IDENTIFIER (
   id-loadablekey |
   id-importablekey |
   id-sealedkey
 )

 TPMKey ::= SEQUENCE {
   type        TPMKeyType,
   emptyAuth   [0] EXPLICIT BOOLEAN OPTIONAL,
   policy      [1] EXPLICIT SEQUENCE OF TPMPolicy OPTIONAL,
   secret      [2] EXPLICIT OCTET STRING OPTIONAL,
   authPolicy  [3] EXPLICIT SEQUENCE OF TPMAuthPolicy OPTIONAL,
   description [4] EXPLICIT UTF8String OPTIONAL,
   rsaParent   [5] EXPLICIT BOOLEAN OPTIONAL,
   parent      INTEGER,
   pubkey      OCTET STRING,
   privkey     OCTET STRING
 }

 END
